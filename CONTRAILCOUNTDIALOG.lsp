;;;;;;;[  Continuous Rail Count Dialog  ];;;;;;;;;
;;                                              ;;
;;  Function for counting rails with long       ;;
;;  center lines. Uses a dialog box to select   ;;
;;  the rigth layer for the lines.              ;;
;;                                              ;;
;;::::::::::::::::::::::::::::::::::::::::::::::;;
;;                                              ;;
;;  Author: J.D. Sandifer  (Copyright 2016)     ;;
;;  Written: 02/03/2016                         ;;
;;                                              ;;
;;;;;;;;;;;;;;;;;;;;;;;;;;;;;;;;;;;;;;;;;;;;;;;;;;
;;                                              ;;
;;  02/03/2016                                  ;;
;;  - Started with the dialog box.              ;;
;;                                              ;;
;;  Todo:                                       ;;
;;  -          ;;
;;                                              ;;
;;;;;;;;;;;;;;;;;;;;;;;;;;;;;;;;;;;;;;;;;;;;;;;;;;


                  
;;; JD:ClearHash - Copyright 2016 J.D. Sandifer

(defun C:ContRailCountDialog ( /  )
	
	(princ "Hi there!")
	
	
	
	
	; silent end
	(princ))

; silent load
(princ)
