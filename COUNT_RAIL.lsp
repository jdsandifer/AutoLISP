;;;;;;;[  Top Rail Count Subfunstion  ];;;;;;;;;;;
;;                                              ;;
;;  Does cut list count based on measurements   ;;
;;  of center lines. Prompts for stock length   ;;
;;  and multiplier and stores in global         ;;
;;  variables.                                  ;;
;;    (forked from RAIL_COUNT_COM)              ;;
;;    (forked from RAIL_COUNT_SPLIT)            ;;
;;                                              ;;
;;::::::::::::::::::::::::::::::::::::::::::::::;;
;;                                              ;;
;;  Author: J.D. Sandifer  (Copyright 2016)     ;;
;;  Written: 11/17/2015                         ;;
;;                                              ;;
;;;;;;;;;;;;;;;;;;;;;;;;;;;;;;;;;;;;;;;;;;;;;;;;;;
;;                                              ;;
;;  08/30/2016                                  ;;
;;  - Finished CountRailParts.                  ;;
;;  - Added ListRemove & ListSearch (temp.).    ;;
;;  - Then moved them to FUNCTIONS.             ;;
;;  - Added unit tests.                         ;;
;;  - Fixed all functions to use new sorts,     ;;
;;    and so on?                                ;;
;;  - Tweaked RailCountSub to use               ;;
;;    CountRailParts.                           ;;
;;                                              ;;
;;  08/29/2016                                  ;;
;;  - Added CountRailParts.                     ;;
;;                                              ;;
;;  08/24/2016                                  ;;
;;  - Added total length display.               ;;
;;  - Added picket panel option for infill.     ;;
;;                                              ;;
;;  04/06/2016                                  ;;
;;  - Tweaked chopping function to fix bug.     ;;
;;  - Added CountStockLengths to simplify       ;;
;;    what I was typing into the command line.  ;;
;;                                              ;;
;;  02/08/2016                                  ;;
;;  - Tweaked chopping function to fix bug.     ;;
;;                                              ;;
;;  02/04/2016                                  ;;
;;  - Did a lot of simplifying                  ;;
;;  - Changed CountRails to create a list for   ;;
;;    the counts instead of printing them.      ;;
;;  - Created PrintCutList to print the data    ;;
;;    so there's no change in function.         ;;
;;                                              ;;
;;  01/31/2016                                  ;;
;;  - Changed to be a subfunction of            ;;
;;    PartsCount.                               ;;
;;  - Fixed the glitch with the first/stock     ;;
;;    lengths not combining into one line       ;;
;;    correctly.                                ;;
;;                                              ;;
;;  11/18/2015                                  ;;
;;  - Revised algorithms for counting and       ;;
;;    measuring to be more precise.             ;;
;;  - Fixed the glitch with the first/stock     ;;
;;    lengths not combining into one line       ;;
;;    correctly.                                ;;
;;                                              ;;
;;  11/17/2015                                  ;;
;;  - Added layer prompt option.                ;;
;;  - Added layer variable to SSGET.            ;;
;;  - Refined prompts - some actions set        ;;
;;    option to next logical choice.            ;;
;;  - Set defaults for options - 242",          ;;
;;    1 floor, Center layer.                    ;;
;;  - Changed display to show duplicate cuts    ;;
;;    as x#.                                    ;;
;;                                              ;;
;;  Todo:                                       ;;
;;  - Untangle layer setting from               ;;
;;    MeasureLineSegments.                      ;;
;;  - MVP best practice - cuts to a list to     ;;
;;    pass to a display function. Where else    ;;
;;    do I need to separate things like that?   ;;
;;  - Re-org everything for easy reading &      ;;
;;    logic, and add comments.                  ;;
;;  - Add post spacing prompt to better figure  ;;
;;    out remainder lengths on chops.           ;;
;;  - Add stair function. And manual mode.      ;;
;;  - Fix bug in chopping function that leaves  ;;
;;    longer than stock length pieces.          ;;
;;                                              ;;
;;;;;;;;;;;;;;;;;;;;;;;;;;;;;;;;;;;;;;;;;;;;;;;;;;
;;                                              ;;
;;  Global variables referenced:                ;;
;;    *stockLength*      *cutList*              ;;
;;    *postSpacing*                             ;;
;;                                              ;;
;;;;;;;;;;;;;;;;;;;;;;;;;;;;;;;;;;;;;;;;;;;;;;;;;;


; Runs all unit tests for this file
; Output: T if all unit tests passed, else nil

(defun C:TestCountRail ( / testList)
	;; Setup for tests
	(princ "\n")
	(princ "Testing COUNT_RAIL\n")
	(princ "--------------------\n")
	
	;; Actual tests
	(princ "CountRailParts\n")
	(Assert 'CountRailParts '('() 240) '())
	(Assert 'CountRailParts '('((240 . 1)) 240) '((240 . 1)))
	(Assert 'CountRailParts '('((242 . 2)) 242) '((242 . 2)))	
	(Assert 'CountRailParts '('((242 . 1)(180 . 1)) 242) '((242 . 2)))
	(Assert 'CountRailParts '('((242 . 1)(160 . 1)) 242) '((242 . 1)(168 . 1)))		
	(Assert
		'CountRailParts
		'('((242 . 1)(160 . 1)(12 . 1)) 242)
		'((242 . 1)(180 . 1)))	
	(Assert 'CountRailParts '('((242 . 1)(160 . 1)(12 . 2)) 242) '((242 . 2)))			
	(Assert
		'CountRailParts
		'('((242 . 1)(160 . 1)(24 . 2)(12 . 3)) 242)
		'((242 . 2)(12 . 1)))
	(Assert
		'CountRailParts
		'('((36 . 10)(31 . 10)(12.75 . 5)(7.375 . 5)) 222)
		'((222 . 3)(120 . 1)))
		
	;; Displaying the results of the tests
	(JD:PrintTestResults (JD:CountBooleans testList)))
	
		
		
;;; Counts toprail (mlines) and prints list of best cuts for parts list.

(defun C:crp ( / stockLength roundingFactorToprail fudgeFactorToAddToprail 
					  layerToCountToprail selSet)
	
	(setq stockLength 242)
	(setq roundingFactorToprail 2
			fudgeFactorToAddToprail 6
			layerToCountToprail "Detail")
					
	(setq selSet
		(ssget
			(list
				'(0 . "mline,*polyline")
				(cons 8 layerToCountToprail))))
	
	(princ 
		(CountRailParts
			(ChopLongLengths
				(MeasureLineSegments
					roundingFactorToprail 
					fudgeFactorToAddToprail
					(JD:FilterSelectionSet (cons 8 layerToCountToprail) 
						(JD:FilterSelectionSet (cons 0 "mline") selSet)))
				stockLength)
			stockLength)))
					
					
					
;; ChopLongLengths - Cuts all lengths longer than stock length and adds back parts. 
;; cutList - [association list] The cut list.

(defun ChopLongLengths (cutList stockLength / currentCutIndex currentCutLength
			currentCutQuantity multiplier remainder finalCutList splices
			MIN-CHOP-LENGTH ROUND-UP-LENGTH)

	(setq MIN-CHOP-LENGTH 87
			ROUND-UP-LENGTH 24)
			
			
   (princ "\nStock length: ")
   (princ stockLength)
   
   (setq currentCutIndex 0)
	(setq finalCutList nil)
	(setq splices 0)
	
   (while (< currentCutIndex (length cutList))

      (setq currentCutLength (car (nth currentCutIndex cutList)))
      (setq currentCutQuantity (cdr (nth currentCutIndex cutList)))

      (if (> currentCutLength stockLength)
			(progn
				(princ "\n= ")
				(princ currentCutQuantity)
				(princ " x ")
				(princ currentCutLength)
				(princ ", ")
				(setq multiplier (fix (/ currentCutLength stockLength)))
				(princ multiplier)
				(setq splices (+ splices (* multiplier currentCutQuantity)))
					; how many stock lengths do we need (per long length)?
				(princ ", ")
				(setq remainder
					(RoundUpTo 2 (rem currentCutLength stockLength)))
				(princ remainder)
					; what's left over after the chop?
				(setq cutList
					(vl-remove (assoc currentCutLength cutList) cutList))
					; remove the long piece
				(setq finalCutList
					(Assoc+Qty stockLength finalCutList
								  (* multiplier currentCutQuantity)))
					; add the stock lengths
				(cond
					; if it's too small, make it long enough (66")
					(	(<= remainder MIN-CHOP-LENGTH)
						(setq finalCutList (Assoc+Qty MIN-CHOP-LENGTH finalCutList 
													currentCutQuantity)))
					; make sure we don't add to greater than stock length
					(	(and
							(> remainder MIN-CHOP-LENGTH)
							(<= remainder (- stocklength ROUND-UP-LENGTH)))
						(setq finalCutList (Assoc+Qty (+ remainder ROUND-UP-LENGTH)
												 finalCutList
												 currentCutQuantity)))
					; if the remainder is long enough, add a stock length, too
					(	(> remainder (- stocklength ROUND-UP-LENGTH))
						(setq finalCutList (Assoc+Qty stockLength finalCutList
								  currentCutQuantity)))))
			(progn
				(setq finalCutList 
					(Assoc+Qty currentCutLength finalCutList currentCutQuantity))
				(setq currentCutIndex (1+ currentCutIndex))))
				
      (princ) )
		
	(JD:DisplayAssocList finalCutList)
	
	(princ "Total length of rail needed: ")
	(setq inches
		(reduce
			'+ 
			(map 
				'(lambda (x) (* (car x) (cdr x))) 
				finalCutList)))
	(princ (RoundUpByDbl 0.5 (/ inches 12.0)))
	(princ "' (")
	(princ inches)
	(princ "\")")

	(princ "\nSplices needed: ")
	(princ splices)
	(princ " (")
	(princ (* 2 splices))
	(princ " splice plates)")
	(princ "\n")
		
   (SortKeys finalCutList '>))



;CountRailParts - choose best part list cuts to fulfill quantities needed
;Arg: cutlist [list] - sorted descending qtylist of needed cuts in inches
;		stocklength [int] - in inches
;Ret: [qtylist] - list of parts list lengths needed (whole feet only) in inches

(defun CountRailParts (cutList stockLength / newCutList itemLen addIndex)
	(setq newCutList '())
	(while (> (length cutList) 0)
		(setq first (car (car cutList)))
		(setq cutList (Assoc-- first cutList))
		(setq itemLen (- stocklength first))
		(setq addIndex (ListSearch '(>= itemLen (car (nth i theList))) cutList))
		(cond
			(	addIndex
				(setq first (+ first (car (nth addIndex cutList))))
				(setq cutList (Assoc-- (car (nth addIndex cutList)) cutList))
				(setq cutList (Assoc++ first cutList))
				(setq cutList (SortKeys cutList '>)))
			(	T
				(cond 
					(	(and (>= stocklength first) (< (* 0.74 stocklength) first))
						(setq newCutList (Assoc++ stocklength newCutList)))
					(	T
						(setq first (RoundUpBy 12 first))
						(setq newCutList (Assoc++ first newCutList)))))))
	(setq newCutList (SortKeys newCutList '>)))
	
	
	
; Menu based system to create a global cutlist with the ability to multiply
; each measurement by a multiplier for multiple similar runs only drawn once
; Arg: none
; Ret: none
; FX:  creates a cut list (qty list) in *cutList*
;      can also calculate stock lengths needed and will print info to cmd line	
	
(defun RailCountSub ( / floorsMultiplier timeToReturn input 			
								roundingFactorToprail fudgeFactorToAddToprail 
								layerToCountToprail selSet addlist)
   ;; Save system variables
	(JD:SaveVar "osmode" 'systemVariables)
	(JD:SaveVar "dimzin" 'systemVariables)
	(princ "System variables saved.")
   
   ;; Set defaults (only do global variables if they aren't set yet)
	(setq roundingFactorToprail 2
			fudgeFactorToAddToprail 0
			layerToCountToprail "Center")
			
   (MakeVarNotNil '*stockLength* 240)
   (MakeVarNotNil '*ctrLineLayer* "Detail")
   (MakeVarNotNil '*choice* "Add")
	(setq floorsMultiplier 1)
	(princ "variable setup")

   (while (/= timeToReturn "True")
   	(initget "Stock Multiplier Layer Add Count RESET Done")
		(setq *choice*
			(cond
				((getkword
					(strcat "\nChoose cut list option [Stock/Multiplier/"
							  "Layer/Add/Count/RESET/Done] <" *choice* ">:" )))
			(*choice*)))
		
		(cond
			(	(= *choice* "RESET")
				(setq *fullCutList* nil)
				(princ *fullCutList*)
				(setq *choice* "Add"))

			(	(= *choice* "Done")
				(setq timeToReturn "True")
				(setq *choice* "RESET"))

			( 	(= *choice* "Stock")
				(setq *choice* "Add")
				(initget (+ 2 4))				; prevent 0 or negative values
				(setq *stockLength*
					(cond
						((getint (strcat "\nStock length (in inches) <" 
											  (itoa *stockLength*)
											  ">:")))
						(*stockLength*))) )

			( 	(= *choice* "Multiplier")
				(setq *choice* "Add")
				(initget (+ 2 4))				; prevent 0 or negative values
				(setq floorsMultiplier
					(cond
						((getint
							(strcat "\nNumber of identical floors (multiplier) <" 
									  (itoa floorsMultiplier)
									  ">:")))
						(floorsMultiplier))))

			( 	(= *choice* "Layer")
				(setq *choice* "Add")
				(setq input (getstring (strcat "\nCenter line layer <"
														 *ctrLineLayer*
														 ">:")))
				(if (/= input "")
					(setq *ctrLineLayer* input)))
			
			( 	(= *choice* "Add")
			
				(setq selSet
					(ssget
						(list
							'(0 . "mline,*polyline")
							(cons 8 layerToCountToprail))))
							
				(setq addList
					(MeasureLineSegments
							roundingFactorToprail 
							fudgeFactorToAddToprail
							(JD:FilterSelectionSet (cons 8 layerToCountToprail) 
								(JD:FilterSelectionSet (cons 0 "*polyline") selSet))))
								
				(setq *fullCutList*
					(AssocAppend *fullCutList* 
						(Assoc* floorsMultiplier addList)))
						
				(setq *fullCutList* (SortKeys *fullCutList* '>))

				(princ "\nCutlist: ")
				(DisplayCount *fullCutList*))
		
			( 	(= *choice* "Count")
				(setq *choice* "Done")
				(setq *cutlist* ;|(ChopLongLengths |;*fullCutList*);)
				
				;; Display & counting handled in these functions
				(princ "\nCutlist: ")
				;(PrintCutList *fullCutList*)
				(DisplayCount *cutList*)
				(princ "\nStock parts list: ")
				(JD:DisplayQtyList (CountRailParts *cutList* *stockLength*)))))

   ;; Restore changed system variables
   (JD:ResetVar "osmode" 'systemVariables)
   (JD:ResetVar "dimzin" 'systemVariables)
   
	qtyNeeded)



;;; Counts toprail (mlines) and infill/bottom rail (plines). Old version...

(defun C:cr ( / stockLength roundingFactorToprail picketList picketChart
					 roundingFactorInfill layerToCountToprail 
					 fudgeFactorToAddToprail fudgeFactorToAddInfill 
					 layerToCountInfill selSet subset isConfirmed infillType
					 roundingFactorPicket fudgeFactorToAddPicket layerToCountPicket
					 totalPickets totalPicketLength infillList inches)
	
	(setq stockLength 242)
	(setq roundingFactorToprail 2
			fudgeFactorToAddToprail 6
			layerToCountToprail "Detail")
	(setq roundingFactorInfill 2
			fudgeFactorToAddInfill 0
			layerToCountInfill "Center")
	(setq roundingFactorPicket 1
			fudgeFactorToAddPicket 2
			layerToCountPicket "Center")
	(setq infillType "Picket")
				
				
	(setq selSet
		(ssget
			(list
				'(0 . "mline,*polyline")
				(cons 
					8 
					(strcat 
						layerToCountToprail 
						","
						layerToCountInfill
						","
						layerToCountPicket)))))
	
	(princ "\nTop rail parts:\n")
	(JD:DisplayQtyList
		(CountRailParts 
			(ChopLongLengths
					(MeasureLineSegments
						roundingFactorToprail 
						fudgeFactorToAddToprail
						(JD:FilterSelectionSet (cons 8 layerToCountToprail) 
							(JD:FilterSelectionSet (cons 0 "mline") selSet)))
					stockLength)
			stockLength))
	
	
	(setq infillList
		(MeasureLineSegments
			roundingFactorInfill
			fudgeFactorToAddInfill
			(JD:FilterSelectionSet (cons 8 layerToCountInfill)  
				(JD:FilterSelectionSet (cons 0 "*polyline") selSet))))
	(setq inches
		(reduce
			'+ 
			(map 
				'(lambda (x) (* (car x) (cdr x))) 
				infillList)))
	(princ
		(strcat "\nTotal length of infill needed: "
			(rtos 
				(RoundUpByDbl 
					0.5 
					(/ inches 12.0))
				2
				2)
			"' ("
			(itoa inches)
			"\")"))			
	(princ "\nInfill/bottom rail parts:\n") 
	(JD:DisplayQtyList 
		(CountRailParts
			infillList
			stockLength))
	(princ)
	
	
	(cond		
		(	(= infillType "Picket")
			(setq picketList
				(MeasureLineSegments
					roundingFactorPicket
					fudgeFactorToAddPicket
					(JD:FilterSelectionSet (cons 8 layerToCountPicket)  
						(JD:FilterSelectionSet (cons 0 "*polyline") selSet))))
			(setq picketChart '(	(22 . 4)
										(27 . 5)
										(31 .	6)
										(36 .	7)
										(40 .	8)
										(45 .	9)
										(50 .	10)
										(54 .	11)
										(59 . 12)
										(64 .	13)
										(68 .	14)
										(73 .	15)
										(77 .	16)
										(1000 . 200) )) ;last one is just a buffer item
			(setq totalPicketLength 0
					totalPickets 0)
			(foreach picketPair picketList
				(setq index 0)
				(while (< (car (nth index picketChart)) (car picketPair))
					(setq index (1+ index)))
				(setq totalPicketLength
					(+ 
						(* (cdr picketPair) (car (nth index picketChart)))
						totalPicketLength))
				(setq totalPickets 
					(+ 
						(* 
							(cdr picketPair) 
							(cdr (nth index picketChart)))totalPickets)))
			(princ
				(strcat
					"\nTotal pickets: "
					(itoa totalPickets)
					"\nTotal picket length: "
					(rtos (RoundUpByDbl 0.5 (/ totalPicketLength 12.0)) 2 2)
					"'"))))
			
		(princ))
		
		
		
;;; Heading towards obsoletion...retained for reference unti sure	
	
;;; CountRails
;;; Determines stock lengths needed to fulfill quantities of rail in cutList.
;;; cutList - [association list] (Length . qtyNeeded) list of railing cuts 
;;; (must be shorter than stock length).
;;; Returns an association list of stock lengths starting with full length
;;; (like cutList).

(defun CountRails ( cutList stockLength / 
						 stockLengthLeft currentCutIndex stockLengthsNeeded currentCutKey bladeWidth); finalCuts finalCutList)

   ;Counters
   (setq stockLengthLeft 0.000)
   (setq currentCutIndex 0)
   (setq stockLengthsNeeded 0)	; will become association list (currently integer)
   (setq bladeWidth 0.125)
	
;;;;prep for full cut list counting
   (setq finalCuts nil)
	(JD:ClearHash 'finalCutList)
	(JD:ClearHash '*fullCutList*)

   (while (> (length cutList) 0)
      
      (setq currentCutLength (car (nth currentCutIndex cutList)))
      
      (cond
			;; Cut length is too long
			((> currentCutLength stockLength)
				(*error*
				(strcat "Problem: Current cut ("
				(itoa currentCutLength)
				"\") is longer than stock length ("
				(itoa stockLength) "\")."))
				(setq cutList nil))
	      
			;;no more length
			((<= stockLengthLeft 0)
				(setq stockLengthLeft stockLength)
				(setq stockLengthsNeeded (1+ stockLengthsNeeded)))
	 
			;;there is more length, but cut won't fit
			((and (> stockLengthLeft 0)
					(> currentCutLength stockLengthLeft))
				(setq currentCutIndex (1+ currentCutIndex)))
	    
			;;there is more length and cut will fit
			((and (> stockLengthLeft 0) (<= currentCutLength stockLengthLeft))
            ;subtract cut length from stock length
				(setq stockLengthLeft (- stockLengthLeft currentCutLength bladeWidth))
            ;;add this cut to the full cut list			
				(setq finalCuts (append finalCuts (list currentCutLength)))
				(JD:PutHash "cuts" (list finalCuts) 'finalCutList)

            ;decrement cut length quantity (or remove from list) - function
				(setq cutList (assoc-- currentCutLength cutList))))

      ;;end of cut list
      (cond
			((or (>= currentCutIndex (length cutList))
				  (<= stockLengthLeft 0)
				  (<= (length cutList) 0))
				(setq currentCutIndex 0)
										
				;;add scrap to the full cut list and prep for the next loop
				(if (= stockLengthLeft -0.125)
					(JD:PutHash "scrap" 0 'finalCutList)
					(JD:PutHash "scrap" stockLengthLeft 'finalCutList))
				(setq *fullCutList* (append *fullCutList* (list finalCutList)))
				(setq finalCuts nil)
				(JD:ClearHash 'finalCutList)

				(setq stockLengthLeft 0)))) ;end of while loop	
				
   stockLengthsNeeded)
		
		
	
;;; Heading towards obsoletion...retained for reference unti sure
	
; MeasureCenterLines
; Created: 10/29/2015 by J.D. Sandifer
; Purpose: Measures lengths of lines on *ctrLineLayer* layer and returns a 
; list of their lengths.
; Input: User selects area contaning the lines.
; Returns: A list of lengths.
; Revision History:
; 10/30/15 - Measuring works! (for one line)

(defun MeasureCenterLines (/ buffer selSet centerline
			     centerLineInfo centerLinelength cutList)

   (setq buffer 6)
   (setq selSet (ssget (list (cons 8 *ctrLineLayer*) '(0 . "line"))))
      ; have the user select an area that includes the lines to measure
      ; and filter in only lines on "A-HRAL-CNTR" layer (not case-sensitive)
   (setq index 0)
   (while (< index (sslength selSet))
      ; loop through the selection set
      (setq centerLine (ssname selSet index))
         ; get the next center line from the list
      (setq centerLineInfo (entget centerLine))
         ; get the entity info list for the line
      (setq centerLinelength
         (distance
            (cdr (assoc 10 centerLineInfo))
            (cdr (assoc 11 centerLineInfo))
               ; access the info at keys 10 & 11 (start and end points),
   	       ; chop off the key so its just the points,
         )
            ; measure the distance between the two points,
	 
      )
         ; and assign it to centerLineLength
      (setq centerLineLength (+ buffer centerLineLength))
         ; add buffer to centerLineLength
      (setq centerLineLength (RoundUpTo 2 centerLineLength))
         ; round up to the nearest 3"
      (setq cutList (Assoc+Qty centerLinelength cutList floorsMultiplier))
	 ; and add it to cutList
      (setq index (1+ index))
         ; increment counter (very important)
   )
      ; end of while loop

   (SortKeys cutlist '>)
   
)


   
;;; Heading towards obsoletion...retained for reference unti sure	
	
;;; PrintCutList - Copyright 2016 J.D. Sandifer
;;; Prints cut list to the command line in a nice format.
;;; cutList [full cut list] - the full cut list

(defun PrintCutList ( cutList / 
							 repeats lastItem currentItem cut)
	(princ "\n")
   (princ "\nStock length cuts")
   (princ "\n--------------------")
	
	(setq repeats 1)
	(setq lastItem nil)
	
	(if (/= cutList nil)
		(progn
			(setq cutList (append cutList '("end")))
			(foreach currentItem cutList
				(if (equal currentItem lastItem)
					(setq repeats (1+ repeats))
					(progn
						(cond ((/= lastItem nil)
							(princ "\n")
							(foreach cut (car (JD:GetHash "cuts" 'lastItem))
								(princ cut)
								(princ " / "))
							(princ "(")
							(princ (JD:GetHash "scrap" 'lastItem))
							(princ ")")
							(if (> repeats 1)
								(princ (strcat " x " (itoa repeats))))
							(setq repeats 1)))))
				(setq lastItem currentItem)))
		(princ "\n   (nothing)"))
		
	(princ "\n--------------------")
	(princ "\n")
	(princ))




;;----------------------------------------------------------------------;;


(princ
    (strcat
        "\n:: COUNT_RAIL.lsp loaded. | \\U+00A9 J.D. Sandifer "
        (menucmd "m=$(edtime,0,yyyy)")
        " ::"))
(princ)

;;----------------------------------------------------------------------;;
;;                             End of File                              ;;
;;----------------------------------------------------------------------;;
